FME workspace wasmachineHyDAMO.fmw

Parameters:
- SourceDataset_XLSXR = $(FME_MF_DIR)DAMO2.2 - HyDAMO.xlsx   # BRON: Microsoft Excel File(s)
- PARAMETER_Waterbeheerder = 14
- PARAMETER =   # Parameter Group
- SourceDataset_OGCGEOPACKAGE_5 =   # BRON: GeoPackage File
- FEATURE_TYPES =
- PARAMETER_2 =   # Parameter Group 2
- SourceDataset_FILEGDB =   # BRON: File Geodatabase
- FEATURE_TYPES_2 =
- PARAMETER_4 =   # Parameter Group 4
- CONNECTION_FILE_GEODATABASE_SDE = C:\Users\sschreuder\Documents\ArcGIS\Projects\DAMO\DAMO_W@O19TST3.sde   # BRON: Damo database - Connection File
- FEATURE_TYPES_3 =
- PARAMETER_5 =   # Parameter Group 5
- SourceDataset_ORACLE_NONSPATIAL =   # Bron: DAMO_CONNECT - Database Connection
- FEATURE_TYPES_4 =
- PARAMETER_3 =   # "" Parameter Group 3
- DestDataset_OGCGEOPACKAGE_5 = C:\Users\sschreuder\Desktop\Wasmachine\Wasmachine 20\output\20230331HyDAMO.gpkg   # GeoPackage File

Readers:
- XLSXR_2: XLSXR from $(SourceDataset_XLSXR)
- OGCGEOPACKAGE_1: OGCGEOPACKAGE from $(SourceDataset_OGCGEOPACKAGE_5)
- FILEGDB_1: FILEGDB from $(SourceDataset_FILEGDB)
- GEODATABASE_SDE_1: GEODATABASE_SDE
- ORACLE_NONSPATIAL_1: ORACLE_NONSPATIAL from $(SourceDataset_ORACLE_NONSPATIAL)

Writers:
- OGCGEOPACKAGE_4: OGCGEOPACKAGE to $(DestDataset_OGCGEOPACKAGE_5) in EPSG:28992

GeometryReplacer
    KIND_LONG = OGC Well Known Text
    OGC_WKT_PRECISION_DISPLAY = 64-bit
    REMOVE_ATTRIBUTE = Yes
    SOURCE = @Value(SHAPE)
    -> StringCaseChanger
Note: Kies 1 van de 4 readers om de workbench te draaien. Indien nodig, zet de andere readers op Disabled.
StringCaseChanger
    ATTRCHOICE = Selected Attributes
    ATTRLIST = fme_feature_type
    CHANGE_TYPE = lowercase
    -> BulkAttributeRenamer
BulkAttributeRenamer
    ATTRCHOICE = All Attributes
    CASE_CHANGE_TYPE = lower
    MODE_CHOICE = RENAME
    PATTERN_ACTION_DISP = CASECHANGE
    -> AttributeCreator_4
Note: Maakt globalid en/of objectid aan indien nodig
AttributeCreator_4
    ATTR_TABLE:
      SET_TO globalid = FME_CONDITIONAL:DEFAULT_VALUE'{@UUID()}'BOOL_OP;OR;COMPOSITE_TEST;1;TEST globalid ATTRIBUTE_HAS_A_VALUE _FME_BLANK_STRING_'@Value(globalid)'FME_NUM_CONDITIONS2___
      SET_TO objectid = FME_CONDITIONAL:DEFAULT_VALUE'@round(@rand()*1000000000,0)'BOOL_OP;OR;COMPOSITE_TEST;1;TEST objectid ATTRIBUTE_HAS_A_VALUE _FME_BLANK_STRING_'@Value(objectid)'FME_NUM_CONDITIONS2___
      SET_TO fme_feature_type = FME_CONDITIONAL:DEFAULT_VALUE'_FME_NO_OP_'BOOL_OP;OR;COMPOSITE_TEST;1;TEST @Value(fme_feature_type) = Hydroobject_abc'Hydroobject'BOOL_OP;OR;COMPOSITE_TEST;1;TEST @Value(fme_feature_type) = Doorstroomopening'Kunstwerkopening'BOOL_OP;OR;COMPOSITE_TEST;1;TEST @Value(fme_feature_type) = Afsluitmiddel'Regelmiddel'FME_NUM_CONDITIONS4___
    -> TestFilter
Junction_3
    -> AttributeExploder
Junction_2
    -> FeatureJoiner_3 [RIGHT]
Attributen (reader XLSXR_2)
    attributes: doelObject char(28), doelAttribuut char(31), doelAttribuutType char(16), doelDomein char(29)
    -> Junction_4
    -> AttributeFilter
Junction_4
    -> Tester_4
Tester_4
    BOOL_OP = OR
    TEST_CLAUSE = TEST @Value(doelAttribuutType) IN Point,Polygon,Polyline
    TEST_MODE = TEST
    FAILED -> AttributeManager_2
Note: Bronvelden selecteren en hernoemen
AttributeManager_2
    ATTR_TABLE:
      REMOVE versieBron
      RENAME_SET_VALUE doelObject > fme_feature_type
      RENAME_SET_VALUE doelAttribuut > name
      RENAME_SET_VALUE doelAttribuutType > fme_data_type = FME_CONDITIONAL:DEFAULT_VALUE''BOOL_OP;OR;COMPOSITE_TEST;1;TEST doelDomein ATTRIBUTE_HAS_A_VALUE _FME_BLANK_STRING_'fme_buffer'BOOL_OP;OR;COMPOSITE_TEST;1;TEST @Value(fme_data_type) = CharacterString'fme_buffer'BOOL_OP;OR;COMPOSITE_TEST;1;TEST @Value(fme_data_type) = Integer'fme_int32'BOOL_OP;OR;COMPOSITE_TEST;1;TEST @Value(fme_data_type) = Date'fme_datetime'BOOL_OP;OR;COMPOSITE_TEST;1;TEST @Value(fme_data_type) = Decimal'fme_real64'BOOL_OP;OR;COMPOSITE_TEST;1;TEST @Value(fme_data_type) = Real'fme_real64'BOOL_OP;OR;COMPOSITE_TEST;1;TEST @Value(fme_data_type) = Datetime'fme_datetime'FME_NUM_CONDITIONS8___
      RENAME_SET_VALUE doelDomein > DoelKolomDomein
    -> ListBuilder
ListBuilder
    GROUP_BY = fme_feature_type
    LIST_ATTRS_TO_INCLUDE = fme_data_type name
    LIST_NAME = attribute
    -> Junction
Junction
    -> FeatureMerger_2 [SUPPLIER]
Note: Bevat dus voor elk feature ALLE kolommen die in een domein zitten. Bij wegschrijven dus alleen de kolommen pakken die van toepassing zijn
FeatureJoiner_3
    ATTR_CONFLICT_RES = Use Left
    GEOMETRY_HANDLING = Use Right
    JOIN_KEYS = fme_feature_type fme_feature_type AUTO globalid globalid AUTO
    JOIN_MODE = Inner
    JOINED -> FeatureMerger_2 [REQUESTOR]
    UNJOINED_RIGHT -> FeatureMerger_2 [REQUESTOR]
    <REJECTED> -> Tester_2
Tester_2
    BOOL_OP = OR
    TEST_CLAUSE = TEST @Value(fme_rejection_code) = MISSING_RIGHT_KEY
    TEST_MODE = TEST
    PASSED -> FeatureMerger_2 [REQUESTOR]
FeatureMerger_2
    ATTR_ACCUM_MODE = Merge Supplier
    ATTR_CONFLICT_RES = Use Requestor
    IGNORE_NULLS = No
    JOIN_KEYS = @Value(fme_feature_type) @Value(fme_feature_type) AUTO
    MERGE_TYPE = Attributes Only
    PROCESS_DUPS = NO
    REJECT_NULL_MISSING_KEYS = No
    SUPPLIERS_FIRST = No
    MERGED -> AttributeCreator_5
AttributeCreator_5
    ATTR_TABLE = SET_TO nen3610id = NL.WBHCODE.$(PARAMETER_Waterbeheerder).@Value(fme_feature_type).@Value(objectid)
    -> GeometryFilter
GeometryFilter
    FILTER_MODE = SIMPLE
    FILTER_MULTI = FILTER_TYPES]"Point Area Line"]FME_CONTROLLER_QUERY_FILE]]FME_CONTROLLER_CHOICE]Simple
    Point -> Table102 (writer OGCGEOPACKAGE_4)
    Curve -> Table1 (writer OGCGEOPACKAGE_4)
    Area -> Table100 (writer OGCGEOPACKAGE_4)
    <UNFILTERED> -> Table101 (writer OGCGEOPACKAGE_4)
Table102 (writer OGCGEOPACKAGE_4)
Table1 (writer OGCGEOPACKAGE_4)
Table100 (writer OGCGEOPACKAGE_4)
Table101 (writer OGCGEOPACKAGE_4)

Bookmark: Readers
Note: HyDAMO File Geodatabase
AfvoergebiedAanvoergebied (reader FILEGDB_1)
    attributes: OBJECTID objectid, code text(50), globalID globalid, naam text(100), statusObject text(18), hyperlink text(256), opmerking text(2000), namespace text(50), detailNiveauGeometrie int, LVpublicatiedatum date, soortAfvoerAanvoergebied text(18), ordeCode text(100), ordeScope text(52), ordeSystematiek text(36), gerelateerdAfAanvoergebied int, ontstaanswijze text(20), waterafvoer int, oppervlakte double, metadataID guid, lateraleKnoopID guid, se_anno_cad_data blob, Shape_Length double, Shape_Area double, DAMODomeinID guid, DAMODomeinNaam text(100), DAMOKolomID guid, DAMOKolomNaam text(100), DAMONaam text(50), DAMOTabelID guid, DAMOTabelNaam text(100),
      ProfielPuntID guid, aantalDoorstroomopeningen int, actiewaarde double, afslagpeil double, afstand double, afvoerCoefficient double, afvoercoefficient double, aquaductID guid, beginPeriode text(50), bergingsgebiedID guid, bevat int, bochtEnKnikverlies double, bodemWeerstand double, bodemhoogteBenedenstrooms double, bodemhoogteBovenstrooms double, bodemvalID guid, bovengrens double, breedte double, breedteOpening double, bronDefinitie text(256), bronDefinitieLink text(256), bronVulWaarde text(256), brugID guid, categorie text(54), categorieOppwaterlichaam text(9), codeVolgnummer int, conditie text(1000), datumInwinning date, debiet double, definitie text(1000),
      dimensie text(2), doelvariabele text(12), doorstroombreedte double, doorstroomlengte double, doorvaartBreedte double, draineert int, drempelpeil double, duikersifonhevelID guid, eenheid text(256), eenheidActiewaarde text(9), eenheidDoelvariabele text(9), eenheidMeetwaarde text(9), eindPeriode text(50), fieldLength text(50), fieldType text(50), filterUitstroming text(3), flux double, functieGemaal text(24), gemaalID guid, getijdeBeinvloed text(3), grondwaterKoppelLijnID guid, grondwaterKoppelPuntID guid, grondwaterkoppellijnID guid, hoogsteDoorstroombreedte double, hoogsteDoorstroomhoogte double, hoogte double, hoogteBinnenOnderkantBene double, hoogteBinnenOnderkantBov double, hoogteBovenzijde double, hoogteConstructie double,
      hoogteOnderzijde double, hoogteOpening double, hydroObjectGroeperingID guid, hydroObjectID guid, hydrologischerandvoorwaardeID guid, hydroobjectID guid, indPeilRegulPeilScheidend text(8), indicatieComplexeSturing text(19), indicatieWaterkerend text(19), infiltratiefactor double, intreeverlies double, inwinnendeInstantie text(52), inwinningsMethode text(16), kerendeHoogte double, kruinbreedte double, krwStromendID guid, kunstwerkopeningID guid, laagsteDoorstroombreedte double, laagsteDoorstroomhoogte double, lengte double, maximaleCapaciteit double, maximaleHoogteBovenkant double, meetlocatieID guid, meetwaarde double, metendeInstantie text(100), metingOmschrijving text(250), minimaleCapaciteit double, minimaleHoogteBovenkant double, naamspace text(50), natteOmtrek double,
      nauwkeurigheidXY smallint, nauwkeurigheidZ smallint, niveau text(20), normgeparamprofielID guid, ondergrens double, ontwerpBuitenWaterstand double, openingspeil double, openkeerpeil double, oppervlaktewaterlichaamID guid, oppwaterVolgnummer int, opstellingPomp text(23), overlaatOnderlaat text(9), peilafwijkingGebiedID guid, peilgebiedPraktijkID guid, peilgebiedVigerendID guid, persistentie text(11), pompID guid, pompcurve text(256), pomprichting text(8), prioriteit text(6), profielgroepID guid, profiellijnID guid, profielweergave text(26), referentievlak text(15), regelmiddelID guid, regenwaterbufferCompartimentID guid, richting single, rioolgemaalID guid, ruimtelijkeAfbakeningBekend text(3), ruwheid double,
      ruwheidHoog double, ruwheidLaag double, signaleringspeil double, sluitpeil double, soortAandrijving text(19), soortMateriaal text(19), soortMeetpunt text(47), soortOppwaterkwaliteit text(49), soortOppwaterkwantiteit text(36), soortOverspanning text(61), soortParameter text(34), soortProfiel text(36), soortRegelbaarheid text(27), soortRegelmiddel text(18), soortStreefpeil text(27), soortStuw text(24), status text(18), statusLeggerWatersysteem text(19), statusLeggerWaterveiligheid text(19), statusPeilgebied text(19), streefwaarde double, sturingID guid, stuurvariabele text(28), stuwID guid, tekencode text(60), tijd date, typeController text(9), typeHydraulischObject text(10), typeKruising text(8), typeMateriaaRegelmiddel text(19),
      typePomp text(14), typePompschakeling text(9), typeRandvoorwaarde text(26), typeRuwheid text(15), typeSturing text(8), typeWaterkerendeConstructie text(58), uittreeverlies double, uniek text(50), vaarwegID guid, vasteWaarde double, voertAfOp int, vormKoker text(15), vormOpening text(15), vulWaarde text(100), waarde double, waterhoogte double, waterkeringID guid, waterstand double
    -> StringCaseChanger
Note: HyDAMO Geopackage
AfvoergebiedAanvoergebied (reader OGCGEOPACKAGE_1)
    attributes: code text(200), globalID text(50), naam text(200), statusObject int, CREATED_DATE datetime, LAST_EDITED_DATE datetime, hyperlink text(500), administratiefgebied int, soortAfvoerAanvoergebied int, ordeCode text(200), oppervlakte double, lateraleknoopID text(200), afvoerCoefficient double, bochtEnKnikverlies double, breedte double, breedteOpening double, categorieOppwaterlichaam int, doorstroomlengte double, duikersifonhevelID text(200), gemaalID text(200), hoogsteDoorstroombreedte double, hoogsteDoorstroomhoogte double, hoogte double, hoogteBinnenOnderkantBene double, hoogteBinnenOnderkantBov double, hoogteBovenzijde double, hoogteConstructie double, hoogteOnderzijde double, hoogteOpening double, indPeilRegulPeilScheidend int,
      intreeverlies double, kruinbreedte double, kunstwerkopeningID text(200), laagsteDoorstroombreedte double, laagsteDoorstroomhoogte double, lengte double, maximaleCapaciteit double, maximaleHoogteBovenkant double, minimaleHoogteBovenkant double, overlaatOnderlaat int, pompcurve text(200), pomprichting int, richting double, ruwheid double, ruwheidHoog double, ruwheidLaag double, soortRegelbaarheid int, soortRegelmiddel int, soortStuw int, stuwID text(200), typeKruising int, typeRuwheid int, uittreeverlies double, vormKoker int, vormOpening int
    -> StringCaseChanger
Note: DAMO 2.2 - Oracle / SDE
Aansluitconstructie (reader GEODATABASE_SDE_1)
    attributes: OBJECTID integer, SE_ANNO_CAD_DATA blob, CODE char(50), NAAM char(100), STATUSOBJECT smallint, STATUSLEGGERWATERVEILIGHEID smallint, WAARDEBEPALINGAANSLUITING char(100), NAMESPACE char(50), DETAILNIVEAUGEOMETRIE integer, LVPUBLICATIEDATUM date, CREATED_USER char(255), CREATED_DATE date, LAST_EDITED_USER char(255), LAST_EDITED_DATE date, GLOBALID globalid, METADATAID guid, WATERKERINGID guid, HYPERLINK char(256), OPMERKING char(2000), SHAPE.LEN double, AANTALBEDRIJVEN integer, AANTALCOMPARTIMENTEN smallint, AANTALDOORSTROOMOPENINGEN integer, AANTALINWONERS integer, AANTALKABELSLEIDINGEN integer, AANTALOPENINGEN integer, AANTALPOMPEN integer, AANTALWONINGEN integer, AANVOERENDEBRONHOUDER char(5), AANVOERENDEDERDEPARTIJ char(100),
      ACTIEWAARDE double, ACTUEELVOLUME double, ADRES char(50), AFGEKOPPELDVERHARDOPPBEDRIJVEN double, AFGEKOPPELDVERHARDOPPWONINGEN double, AFMETINGPUTSCHACHT integer, AFNAMEVERPLICHTINGIE integer, AFNAMEVERPLICHTINGUURDWA double, AFNAMEVERPLICHTINGUURRWA double, AFSLAGPEIL double, AFSLUITEROVERNAMEPUNT char(1), AFSPRAAKNUMMER char(50), AFSPRAAKNUMMERACTUEEL char(50), AFSTAND float, AFSTANDBEGIN integer, AFSTANDEINDE integer, AFSTANDTOTNULPUNT integer, AFVOERCOEFFICIENT double, AFVOERENDOPPERVLAKBEDRIJVEN double, AFVOERENDOPPERVLAKWONINGEN double, AFVOERRICHTING char(50), ANKERVELDID guid, AQUADUCTID guid, ARTIKEL double, BEDDINGSCONSTANTE double, BEDIENINGSPLICHTIGE smallint, BEDIENINGSVERPLICHTING smallint, BEGINAFSTAND integer, BEGINPERIODE char(50), BEHEERDER smallint,
      BEKLEDINGCONSTRUCTIEID guid, BERGENDVERMOGEN double, BERGINGINRIOLERING double, BERGINGRANDVOORZIENINGREGEN double, BERGINGRANDVOORZIENINGVOLUME double, BERGINGSGEBIEDID guid, BESTORTINGID guid, BEVAT integer, BEWEZENSTERKTEVOORWAARDE1 smallint, BEWEZENSTERKTEVOORWAARDE2 smallint, BEWEZENSTERKTEVOORWAARDE3 smallint, BEWEZENSTERKTEVOORWAARDE4 smallint, BGTFYSIEKVOORKOMEN smallint, BGTSTATUS smallint, BGTTYPE smallint, BIJWETVASTGESTELD char(1), BINNENDIAMETER double, BINNENDIAMETER2 double, BIOLOGISCHECAPACITEIT integer, BOCHTENKNIKVERLIES double, BODEMAFDICHTING char(1), BODEMHOOGTEBENEDENSTROOMS double, BODEMHOOGTEBOVENSTROOMS double, BODEMVALID guid, BODEMWEERSTAND double, BOVENGRENS double, BOVENGRONDSZICHTBAAR char(1), BOVENKANTCONSTRUCTIE double, BREEDTE double, BREEDTEBOUWWERK double,
      BREEDTEINWENDIG integer, BREEDTEOPENING double, BREEDTESTENEN double, BRON char(100), BRONDEFINITIE char(256), BRONDEFINITIELINK char(256), BRONHOUDER char(250), BRONVULWAARDE char(256), BRUGID guid, BUITENDIAMETER double, BUITENDIAMETER2 double, CAPACITEITGEINSTALLEERD double, CAPACITEITHUIDIG double, CAPACITEITONTWERP double, CATEGORIE smallint, CATEGORIEOPPWATERLICHAAM smallint, CATEGORIEWATERKERINGSTELSEL smallint, CODEDOMEINWAARDE char(50), CODEVOLGNUMMER integer, CONDITIE char(1000), COUPUREID guid, DAMODOMEINID guid, DAMODOMEINNAAM char(100), DAMOID guid, DAMOKOLOMID guid, DAMOKOLOMNAAM char(100), DAMOMODELNAAM char(50), DAMONAAM char(50), DAMOTABELID guid, DAMOTABELNAAM char(100),
      DATUMINWINNING date, DATUMVASTELLING date, DEBIET double, DEFINITIE char(1000), DIAMETER double, DIAMETERDRAINAGEBUIS double, DICHTHEIDASFALTMENGSEL double, DIEPTEINGEGOTENTOPLAAG double, DIEPTEKLASSE smallint, DIJKRINGNUMMER char(50), DIKTE double, DIKTEASFALT double, DIKTEKLEILAAG double, DIMENSIE smallint, DOELVARIABELE smallint, DOORLATENDHEIDSTROMING double, DOORLATENDHEIDVERVAL integer, DOORSTROOMBREEDTE double, DOORSTROOMLENGTE double, DOORVAARTBREEDTE double, DOORVAARTNUMMER smallint, DRAINAGEBUISID guid, DRAINAGEPUTID guid, DRAINEERT integer, DREMPELBREEDTE integer, DREMPELDIKTE integer, DREMPELHOOGTE double, DREMPELHOOGTEEXTERN double, DREMPELHOOGTEINTERN double, DREMPELPEIL double,
      DREMPELVORM char(50), DRUKKLASSE smallint, DUIKERSIFONHEVELID guid, DWAAFVOERBEDRIJVEN double, DWAAFVOERINWONERS integer, EENHEID char(256), EENHEIDACTIEWAARDE smallint, EENHEIDDOELVARIABELE smallint, EENHEIDMEETWAARDE smallint, EIGENAAR smallint, EINDPERIODE char(50), EINDREGISTRATIE date, FIELDLENGTH char(50), FIELDTYPE char(50), FILTERUITSTROMING char(2), FLEXIBELEWATERKERINGID guid, FLUX double, FREQUENTIE integer, FUNCTIEAFSLUITMIDDEL smallint, FUNCTIEGEMAAL smallint, FUNCTIEOPPERVLAKTEWATERDEEL smallint, FYSIEKAANWEZIG char(1), GEDRAGGRASZODEBUITENTALUD smallint, GELDIGBEGINTIJD date, GELDIGEINDTIJD date, GEMAALID guid, GEMEENTE char(5), GEMIDDELDHOOGWATER double, GEONAUWKEURIGHEIDXY smallint, GERELATEERDAFAANVOERGEBIED integer,
      GETIJDEBEINVLOED char(1), GEWENSTPERCENTAGEMORTEL range_domain(Percentage:double:1:100), GRADENBOCHT integer, GRASKWALITEIT smallint, GRONDSOORTZODE smallint, GRONDWATERKOPPELLIJNID guid, GRONDWATERKOPPELPUNTID guid, HECTOMETERAANDUIDING char(50), HEEFTRIOOLOVERSTORT char(1), HELLING integer, HELLINGSHOEK double, HOEKVANGOLFINVAL double, HOEVEELHEIDBESTORTING integer, HOOGSTEDOORSTROOMBREEDTE double, HOOGSTEDOORSTROOMHOOGTE double, HOOGTE double, HOOGTEBINNENONDERKANTBEN double, HOOGTEBINNENONDERKANTBENE double, HOOGTEBINNENONDERKANTBOV double, HOOGTEBINNENONDERKANTLEIDING double, HOOGTEBOUWWERK double, HOOGTEBOVENKANT double, HOOGTEBOVENZIJDE double, HOOGTECONSTRUCTIE double, HOOGTEINWENDIG integer, HOOGTEONDERZIJDE double, HOOGTEOPENING double, HOOGTEPUTBODEM double, HOOGTEPUTDEKSEL double, HORIZONTALEKNIK integer,
      HYDRAULISCHECAPACITEIT integer, HYDRAULISCHERANDVOORWAARDEID guid, HYDROLOGISCHERANDVOORWAARDEID guid, HYDROOBJECTGROEPERINGID guid, HYDROOBJECTID guid, IBAID guid, INDICATIECOMPLEXESTURING smallint, INDICATIEDOORVAARBAARHEID char(1), INDICATIEWATERKEREND smallint, INDPEILREGULPEILSCHEIDEND char(1), INFILTRATIEFACTOR double, INFILTRATIEVOORZIENING char(1), INGEWASSEN char(1), INHOUD double, INHOUDVOORZIENINGREGEN double, INHOUDVOORZIENINGVOLUME double, INONDERZOEK char(1), INSTALLATIEDATUM date, INTREEVERLIES double, INWINNENDEINSTANTIE char(5), INWINNINGSINSTANTIE char(50), INWINNINGSMETHODE smallint, INWONEREQUIVALENTBEDRIJVEN integer, INWONEREQUIVALENTINWONERS integer, INWONEREQUIVALENTRECREATIE integer, INWONERSEQUIVALENTBEDRIJVEN integer, INWONERSEQUIVALENTINWONERS integer, INWONERSEQUIVALENTRECREATIE integer, ISZINKER char(1), JAARGELEGD integer,
      JAARTM integer, JAARVAN integer, JAARVANAANLEG smallint, JAARVASTSTELLING integer, KATHODISCHEBESCHERMINGID guid, KERENDEHOOGTE double, KERNOPBOUWID guid, KISTDAMID guid, KLEIKWALITEIT smallint, KORRELVERDELING double, KORRELVERDELINGKLEILAAG range_domain(Percentage:double:1:100), KORRELVERDELINGZANDLAAG range_domain(Percentage:double:1:100), KRUINBREEDTE double, KRWSTILSTAANDID guid, KRWSTROMENDID guid, KUNSTWERKOPENINGID guid, LAAGSTEDOORSTROOMBREEDTE double, LAAGSTEDOORSTROOMHOOGTE double, LAATSTERENOVATIE date, LATERALEKNOOPID guid, LEDIGINGSMETHODE char(50), LEDIGINGSTIJD integer, LEIDINGID guid, LEIDINGIDBRON guid, LEIDINGIDDOEL guid, LEIDINGSEGMENTID guid, LENGTE double, LENGTEBOUWWERK double, LENGTEOPENING double, LENGTESTELSEL integer,
      LIGGING char(50), LOCATIE char(50), LOKATIEGRASBEKLEDING smallint, MAATGEVENDHOOGWATER double, MAXIMALECAPACITEIT double, MAXIMALECAPACITEITUURDWA integer, MAXIMALEHOOGTEBOVENKANT double, MAXIMALEPOMPCAPACITEIT integer, MEETINSTRUMENTID guid, MEETLOCATIEID guid, MEETNETID guid, MEETWAARDE double, METENDEINSTANTIE char(100), METINGOMSCHRIJVING char(250), MILIEUZONE double, MINIMALECAPACITEIT double, MINIMALEHOOGTEBOVENKANT double, MUTEERBAARHEID char(100), MUURVLAK smallint, NAAMDOMEINWAARDE char(250), NAAMSPACE char(50), NAP_BOUT char(500), NATTEOMTREK double, NATUURVRIENDELIJKEOEVERID guid, NAUWKEURIGHEID double, NAUWKEURIGHEIDXY smallint, NAUWKEURIGHEIDZ smallint, NIVEAU smallint, NOMINALESPANNING integer, NOODUITLAATID guid,
      NORM char(50), NORMGEPARAMPROFIELID guid, NORMGROEP smallint, NORMKADER smallint, NORMWAARDE char(50), O90 double, OMSCHRIJVING char(50), OMSCHRIJVINGLOCATIE char(50), ONDERGRENS double, ONDERHOUDOPPEIL char(50), ONDERHOUDSPLICHTIGE smallint, ONDERHOUDSVERPLICHTING smallint, ONDERKANTCONSTRUCTIE double, ONDERLAAG smallint, ONEFFENHEDENHAVENDAM double, ONTSTAANSWIJZE smallint, ONTTREKKINGVOORMENSELIJKECONS char(1), ONTWERPBUITENWATERSTAND double, OPENINGSPEIL double, OPENKEERPEIL double, OPERATIONELESPANNING integer, OPMERKINGEN char(255), OPPERVLAKBEDRIJFSTERREIN double, OPPERVLAKTE double, OPPERVLAKTECOMPARTIMENT double, OPPERVLAKTEWATERLICHAAMID guid, OPPWATERVOLGNUMMER integer, OPSTELLINGPOMP smallint, OPTALUD char(1), ORDECODE char(100),
      ORDESCOPE smallint, ORDESYSTEMATIEK smallint, OVERLAATONDERLAAT smallint, OVERNAMEPUNTID guid, OVERSTORTFREQUENTIE integer, OVERSTORTMESAANWEZIG char(50), PAKKING char(50), PEILAFWIJKINGGEBIEDID guid, PEILBESLUITGEBIEDID guid, PEILGEBIEDPRAKTIJKID guid, PEILGEBIEDVIGERENDID guid, PERCENTAGEBITUMEN range_domain(Percentage:double:1:100), PERCENTAGEHOLLERUIMTE range_domain(Percentage:double:1:100), PERCENTAGESTEENSLAGGRIND range_domain(Percentage:double:1:100), PERCENTAGEVULSTOF range_domain(Percentage:double:1:100), PERCENTAGEZAND range_domain(Percentage:double:1:100), PERSISTENTIE smallint, PIEKPERIODEOFGOLFPERIODE double, PLAATSOPMAATLATDOELSTELLING char(500), PLUSFYSIEKVOORKOMEN smallint, PLUSTYPE smallint, POMPCURVE char(256), POMPID guid, POMPOVERCAPACITEITBESCHIKBAAR double, POMPRICHTING smallint, POROSITEIT double, PRIORITEIT smallint, PROFIELGROEPID guid, PROFIELLIJNID guid, PROFIELPUNTID guid,
      PROFIELWEERGAVE smallint, PROVINCIEREGLEMENT char(5), PUTBODEM double, PUTID guid, RANDVOORZIENINGID guid, REFERENTIENRCBS integer, REFERENTIEPUNTID guid, REFERENTIESTELSELID guid, REFERENTIEVLAK smallint, REGELMIDDELID guid, REGENWATERBUFFERCOMPARTIMENTID guid, REGENWATERBUFFERID guid, RELATIEFOPENOPPERVLAK range_domain(Percentage:double:1:100), RELATIELINK char(512), RELATIEOBJECT char(256), RELATIEVEHOOGTELIGGING smallint, RICHTING float, RID integer, RIOLERINGSGEBIEDID guid, RIOLERINGSGEBIEDIDBRON guid, RIOLERINGSGEBIEDIDDOEL guid, RIOOLGEMAALID guid, RIOOLOVERSTORTID guid, RIOOLVREEMDWATER double, RUIMTELIJKEAFBAKENINGBEKEND char(1), RUWHEID double, RUWHEIDHOOG double, RUWHEIDLAAG double, RWZIID guid, SCHAAL integer,
      SCHADELIJKEBEGROEIING smallint, SEGMENTBREEDTE double, SHAPE.AREA double, SHAPE_LENGTH double, SIGNALERINGSPEIL double, SIGNIFICANTEGOLFHOOGTE double, SLIBBELASTING double, SLUISID guid, SLUITPEIL double, SOORTAANDRIJVING smallint, SOORTAFSLUITER smallint, SOORTAFSLUITMIDDEL smallint, SOORTAFVOERAANVOERGEBIED char(2), SOORTBEKLEDINGCONSTRUCTIE char(2), SOORTELIJKEMASSASTENEN double, SOORTGELOOSDWATER smallint, SOORTKABEL smallint, SOORTKATHODE smallint, SOORTKWANTITEITSMETING smallint, SOORTLEIDING smallint, SOORTMATERIAAL smallint, SOORTMATERIAALOEVER smallint, SOORTMEETINSTRUMENT smallint, SOORTMEETNET smallint, SOORTMEETPUNT smallint, SOORTNATUURVRIENDELIJKEOEVER smallint, SOORTOPPWATERKWALITEIT smallint, SOORTOPPWATERKWANTITEIT smallint, SOORTOVERSPANNING smallint, SOORTOVERSTORT smallint,
      SOORTPARAMETER smallint, SOORTPEILMERK smallint, SOORTPROFIEL smallint, SOORTRANDVOORZIENING smallint, SOORTREFERENTIELIJN smallint, SOORTREGELBAARHEID smallint, SOORTREGELMIDDEL smallint, SOORTREGENWATERBUFFER smallint, SOORTRIOOLGEMAAL smallint, SOORTSLUIS smallint, SOORTSTELSEL smallint, SOORTSTREEFPEIL smallint, SOORTSTUW smallint, SOORTTAAK smallint, SOORTVERBINDINGSSTUK smallint, SOORTVERDEDIGING smallint, SOORTVISPASSAGE smallint, SOORTVUILVANG smallint, SOORTWATER smallint, SOORTWATERINRICHTINGSELEMENT smallint, SOORTZANDVANG smallint, SPLEETBREEDTELANGSVOEGEN double, SPLEETBREEDTESTOOTVOEGEN double, SPONNINGBREEDTE double, STATUS smallint, STATUSKRW char(1), STATUSLEGGERWATERSYSTEEM smallint, STATUSONDERHOUD char(50), STATUSPEILGEBIED smallint, STEENDIAMETER double,
      STRAALBOCHT integer, STREEFWAARDE double, STROMINGSBEGELEIDING smallint, STROOMVOERENDEBREEDTE double, STURINGID guid, STUURVARIABELE smallint, STUWID guid, TAGNAAM char(256), TEENOVERGANGSCONSTRUCTIEID guid, TEKENCODE smallint, TERUGSLAGKLEPAANWEZIG char(50), TIJD date, TOETSPEIL double, TOPLAAGASFALTID guid, TRANSPORTSTELSELID guid, TUNNELID guid, TYPE smallint, TYPEBEDIENING smallint, TYPEBEKLEDINGLAAG smallint, TYPEBODEMLAAG smallint, TYPECONSTRUCTIEOPBOUW smallint, TYPECONTROLLER smallint, TYPEDIJKOPBOUW char(50), TYPEELECTRICITEITSKABEL smallint, TYPEFILTERLAAG smallint, TYPEHYDRAULISCHOBJECT smallint, TYPEIBA smallint, TYPEINVLOEDSLIJN smallint, TYPEKERNOPBOUW smallint, TYPEKRUISING smallint,
      TYPEKWELSCHERM smallint, TYPEMATERIAAL smallint, TYPEMATERIAALAFSLUITMIDDEL smallint, TYPEMATERIAALBEKLEDING smallint, TYPEMATERIAALDRAINAGEBUIS smallint, TYPEMATERIAALZINKSTUK smallint, TYPEMATERIAAREGELMIDDEL smallint, TYPEONDERGROND smallint, TYPEONTLUCHTER smallint, TYPEOVERBRUGGINGSDEEL smallint, TYPEOVERGANGSCONSTRUCTIE smallint, TYPEPIGGINGINSTALLATIE smallint, TYPEPOMP smallint, TYPEPOMPSCHAKELING smallint, TYPEPROFIELKENMERK smallint, TYPERANDVOORWAARDE smallint, TYPEREFERENTIESTELSEL smallint, TYPERUWHEID smallint, TYPERWZI smallint, TYPESTURING smallint, TYPEVERBINDING smallint, TYPEWANDCONSTRUCTIE integer, TYPEWATERKERENDECONSTRUCTIE smallint, TYPEWATERKERING smallint, TYPEWATERKERINGSECTIE smallint, TYPEWATERKERINGSTELSEL smallint, TYPEWETOFVERORDENING smallint, TYPEZONE smallint, TYPOLOGIEHUIDIG char(5), TYPOLOGIEREFNATUURLIJK char(5),
      UITSLAGPEIL double, UITTREEVERLIES double, UNIEK char(50), VAARWEGID guid, VAARWEGKLASSE char(30), VASTEDAMID guid, VASTEWAARDE double, VEGETATIEOBJECTID guid, VERDEDIGINGID guid, VERLORENBERGING double, VERMOGEN integer, VERSIE char(50), VERTICALEKNIK integer, VERVAL double, VERWIJZINGNAARREGLEMENT char(50), VISPASSAGEID guid, VOERTAFOP integer, VOLGNUMMER smallint, VOLUMECOMPARTIMENT double, VOLUMEMATERIAAL double, VOORDEID guid, VORM smallint, VORMBOUWWERK smallint, VORMKOKER smallint, VORMLEIDING smallint, VORMOPENING smallint, VUILVANGID guid, VULLINGSWIJZE smallint, VULTIJDGEBIED double, VULWAARDE char(100),
      WAARDE double, WAARDEMETING double, WAARDEVALDEFLECTIE double, WANDCONSTRUCTIEID guid, WATERAFVOER integer, WATERHOOGTE double, WATERKERINGSTELSELAGGREGATIEID guid, WATERSCHAPCODE smallint, WATERSTAATSWERKWATERKERINGID guid, WATERSTAND double, WEESCONSTRUCTIEID guid, WS_BESTORTINGID integer, WS_DUMMY integer, WS_HYDROOBJECTID integer, WS_METADATAID integer, WS_WATERSTAATSWERKWATERKERINGI integer, XMLNAAM char(250), XMUURVLAKCOORDINAAT double, YMUURVLAKCOORDINAAT double, ZANDVANGID guid, ZANDWATERUITTREDING smallint, ZUIVERINGSEENHEIDID guid
    -> StringCaseChanger
Note: : DAMO 2.2 / DAMO_CONNECT - Oracle
AANSLUITCONSTRUCTIE (reader ORACLE_NONSPATIAL_1)
    attributes: DAMOVERSIE char(4), CODE varchar2(50), CREATED_DATE timestamp(6), DETAILNIVEAUGEOMETRIE number(10,0), GLOBALID varchar2(38), HYPERLINK varchar2(256), LAST_EDITED_DATE timestamp(6), LVPUBLICATIEDATUM timestamp(6), METADATAID varchar2(38), NAAM varchar2(100), NAMESPACE varchar2(50), OBJECTID number(10,0), OPMERKING varchar2(250), SHAPE clob, STATUSLEGGERWATERVEILIGHEID number(38,0), STATUSOBJECT number(38,0), WAARDEBEPALINGAANSLUITING varchar2(100), WATERKERINGID varchar2(38), AANTALBEDRIJVEN number(5,0), AANTALCOMPARTIMENTEN number(5,0), AANTALDOORSTROOMOPENINGEN number(5,0), AANTALINWONERS number(8,0), AANTALKABELSLEIDINGEN number(10,0), AANTALOPENINGEN number(10,0), AANTALPOMPEN number(5,0), AANTALWONINGEN number(10,0), AANVOERENDEBRONHOUDER nvarchar(5), AANVOERENDEDERDEPARTIJ nvarchar(100), ACTUEELVOLUME number(38,8), ADRES nvarchar(50),
      AFGEKOPPELDVERHARDOPPBEDRIJVEN number(8,2), AFGEKOPPELDVERHARDOPPWONINGEN number(8,2), AFMETINGPUTSCHACHT number(10,0), AFNAMEVERPLICHTINGIE number(10,0), AFNAMEVERPLICHTINGUURDWA number(10,2), AFNAMEVERPLICHTINGUURRWA number(10,2), AFSLAGPEIL number(8,2), AFSLUITEROVERNAMEPUNT nvarchar(1), AFSPRAAKNUMMER nvarchar(50), AFSPRAAKNUMMERACTUEEL nvarchar(50), AFSTANDBEGIN number(10,0), AFSTANDEINDE number(10,0), AFSTANDTOTNULPUNT number(10,0), AFVOERCOEFFICIENT number(8,2), AFVOERENDOPPERVLAKBEDRIJVEN number(8,2), AFVOERENDOPPERVLAKWONINGEN number(8,2), AFVOERRICHTING nvarchar(50), ANCESTOR_MOMENT timestamp(3), ANY_PATH varchar2(4000), APPLICATION_ID number(38,0), AQUADUCTID varchar2(38), ARCHIVE_DATE number(38,0), ARCHIVE_FLAGS number(38,0), ARCHIVING_REGID number(38,0), ARTIKEL number(8,2), ATTRIBUTES number(38,0), AUDSID number(38,0), AUTH_NAME varchar2(256), AUTH_SRID number(38,0), AUTOLOCK char(1),
      AVGMBRLEN1 number, AVGMBRLEN2 number, AVGMBRLEN3 number, BACKWARDLABEL nvarchar(257), BASE_ID number(38,0), BASE_LAYER_ID number(38,0), BASE_MAP varchar2(32), BASE_RASTERCOLUMN_ID number(38,0), BASE_TABLE varchar2(260), BEDDINGSCONSTANTE number(8,2), BEDIENINGSPLICHTIGE number(3,0), BEDIENINGSVERPLICHTING number(3,0), BEGINAFSTAND number(10,0), BEGINPERIODE nvarchar(50), BEHAVIOR_MAP raw(16), BEHEERDER number(5,0), BEKLEDINGCONSTRUCTIEID varchar2(38), BERGENDVERMOGEN number(12,0), BERGINGINRIOLERING number(10,2), BERGINGRANDVOORZIENINGREGEN number(10,2), BERGINGRANDVOORZIENINGVOLUME number(10,2), BERGINGSGEBIEDID varchar2(38), BESTORTINGID char(38), BEVAT number(10,0), BEWEZENSTERKTEVOORWAARDE1 number(5,0), BEWEZENSTERKTEVOORWAARDE2 number(5,0), BEWEZENSTERKTEVOORWAARDE3 number(5,0), BEWEZENSTERKTEVOORWAARDE4 number(5,0), BGTFYSIEKVOORKOMEN number(3,0), BGTSTATUS number(3,0),
      BGTTYPE number(3,0), BIJWETVASTGESTELD varchar2(100), BINNENDIAMETER number(10,0), BINNENDIAMETER2 number(8,2), BIOLOGISCHECAPACITEIT number(10,0), BKT_ID number, BLEVEL number, BOCHTENKNIKVERLIES number(8,2), BODEMAFDICHTING nvarchar(1), BODEMHOOGTEBENEDENSTROOMS number(8,2), BODEMHOOGTEBOVENSTROOMS number(8,2), BODEMVALID char(38), BODEMWEERSTAND number(8,2), BOVENGRONDSZICHTBAAR varchar2(100), BOVENKANTCONSTRUCTIE number(8,2), BRANCH_GUID char(38), BRANCH_ID number, BRANCH_MOMENT timestamp(3), BREEDTE number(8,2), BREEDTEBOUWWERK number(38,8), BREEDTEINWENDIG number(5,0), BREEDTEOPENING number(8,2), BREEDTESTENEN number(8,2), BRONHOUDER varchar2(100), BRUGID varchar2(38), BUGFIX number(38,0), BUITENDIAMETER number(10,0), BUITENDIAMETER2 number(8,2), CANROLLBACKTO varchar2(3), CAN_POST number(4,0),
      CAPACITEITGEINSTALLEERD number(9,2), CAPACITEITHUIDIG number(7,2), CAPACITEITONTWERP number(7,2), CAPTURE varchar2(3), CATEGORIE number(5,0), CATEGORIEOPPWATERLICHAAM number(3,0), CATEGORIEWATERKERINGSTELSEL number(5,0), CATEGORY nvarchar(128), CDATE number(38,0), CHARACTER_SET number, CHAR_PROP_VALUE nvarchar(512), CHILD_LAYER_ID number, CHK_OPTION varchar2(3), CHUNK_ID number, CHUNK_NAME varchar2(87), CHUNK_UNIQUE_ID number, CLASS_NAME nvarchar(32), CLOSING_TIME date, CLUSTERING_FACTOR number, CMPD_HORIZ_SRID number(10,0), CMPD_VERT_SRID number(10,0), CODEVOLGNUMMER number(5,0), COLUMN_EXPRESSION clob, COLUMN_ID number(38,0), COLUMN_LENGTH number, COLUMN_NAME varchar2(2048), COLUMN_POSITION number, COLUMN_SIZE number(38,0), COL_IDX_IN_KEY number, COL_NAME varchar2(128),
      COL_SIZE number, COL_TYPE number, COMMIT_INT number(38,0), CONCAT_OPERATION_ID number(10,0), CONFIG_KEYWORD nvarchar(32), CONFIG_STRING nclob, CONFLICT varchar2(4000), CONFLICT_TYPE number(38,0), CONSTRAINT_NAME varchar2(128), CONSTRAINT_TYPE varchar2(2), CONSTR_NAME varchar2(128), CONSTR_OWNER varchar2(128), CONTEXT raw(4), CONTINGENTVALUES blob, CONTINUALLY_REFRESHED varchar2(3), CONVERSION_FACTOR number, COORD_AXIS_ABBREVIATION varchar2(24), COORD_AXIS_NAME varchar2(80), COORD_AXIS_NAME_ID number(10,0), COORD_AXIS_ORIENTATION varchar2(24), COORD_DIMENSION number, COORD_OP_ID number, COORD_OP_METHOD_ID number(10,0), COORD_OP_METHOD_NAME varchar2(50), COORD_OP_NAME varchar2(80), COORD_OP_TYPE varchar2(24), COORD_OP_VARIANT number(5,0), COORD_REF_SYS_KIND varchar2(24), COORD_REF_SYS_NAME varchar2(80), COORD_SYS_ID number(10,0),
      COORD_SYS_NAME varchar2(254), COORD_SYS_TYPE varchar2(24), COORD_TFM_VERSION varchar2(24), COORD_TXFM_SRC_SRID number, COORD_TXFM_TGT_SRID number, COUPUREID varchar2(38), CREATED_USER nvarchar(255), CREATETIME timestamptz(6), CREATE_DATE date, CREATION_DATE date, CREATION_TIME timestamp(3), CREATOR varchar2(128), CS_ID number(38,0), CS_NAME varchar2(80), CS_TYPE nvarchar(128), CT_COLS varchar2(4000), CT_NAME varchar2(128), CT_OWNER varchar2(128), CURRENT_SESSION varchar2(3), DATABASE_NAME nvarchar(128), DATASETINFO1 nvarchar(255), DATASETINFO2 nvarchar(255), DATASETSUBTYPE1 number(38,0), DATASETSUBTYPE2 number(38,0), DATA_DIMS number, DATA_SOURCE varchar2(40), DATA_TYPE number(38,0), DATE_VAL date, DATUMINWINNING timestamp(6), DATUMVASTELLING timestamp(6),
      DATUM_ID number(10,0), DATUM_NAME varchar2(80), DATUM_TYPE varchar2(24), DBL_VAL float, DEBIET number(8,2), DECIMAL_DIGITS number(38,0), DEFAULTS blob, DEFAULT_MOMENT timestamp(6), DEFINITION clob, DEF_VERSION number, DEL varchar2(3), DELETE_RULE varchar2(1), DEL_BB_END1 number, DEL_BB_END2 number, DEL_BB_END3 number, DEL_BB_END4 number, DEL_BB_START1 number, DEL_BB_START2 number, DEL_BB_START3 number, DEL_BB_START4 number, DEL_NO number, DENSITY number, DESCEND varchar2(4), DESCRIPTION varchar2(4000), DESTID char(38), DESTITEMTYPEID char(38), DIAMETER number(10,0), DIAMETERDRAINAGEBUIS number(8,2), DICHTHEIDASFALTMENGSEL number(8,2), DIEPTEINGEGOTENTOPLAAG number(8,2),
      DIEPTEKLASSE number(5,0), DIFF varchar2(4000), DIGITS_RIGHT_OF_DECIMAL number, DIJKRINGNUMMER nvarchar(50), DIKTE number(8,2), DIKTEASFALT number(8,2), DIKTEKLEILAAG number(8,2), DIMENSIE number(5,0), DIMENSION number(5,0), DIM_POS number, DIM_UNIT varchar2(32), DIRECT_CONNECT varchar2(1), DISTINCT_KEYS number, DML varchar2(3), DML_CHAR number, DOCUMENTATION number(38,0), DOC_ID number(38,0), DOC_NAME varchar2(100), DOC_PROPERTY number(38,0), DOC_TYPE varchar2(100), DOC_TYPE_DSC varchar2(4000), DOORLATENDHEIDSTROMING number(8,2), DOORLATENDHEIDVERVAL number(5,0), DOORSTROOMBREEDTE number(8,2), DOORVAARTBREEDTE number(8,2), DOORVAARTNUMMER number(5,0), DRAINAGEBUISID char(38), DRAINAGEPUTID char(38), DRAINEERT number(10,0), DREMPELBREEDTE number(5,0),
      DREMPELDIKTE number(5,0), DREMPELHOOGTE number(8,2), DREMPELHOOGTEEXTERN number(10,2), DREMPELHOOGTEINTERN number(10,2), DREMPELPEIL number(8,2), DREMPELVORM nvarchar(50), DRUKKLASSE number(2,0), DUIKERSIFONHEVELID varchar2(38), DWAAFVOERBEDRIJVEN number(8,2), DWAAFVOERINWONERS number(8,0), EDGE_SEQUENCE varchar2(27), EDIT_MOMENT timestamp(3), EENHEID number(3,0), EFF_TYPE number, EFLAGS number(38,0), EIGENAAR number(5,0), EINDPERIODE nvarchar(50), EINDREGISTRATIE timestamp(6), ELLIPSOID_ID number(10,0), ELLIPSOID_NAME varchar2(80), ENABLE varchar2(3), END1 number, END2 number, END3 number, END_1 number, END_2 number, END_3 number, END_4 number, ERRORCODE number(38,0), ERROR_MSG varchar2(200),
      EVENT number(38,0), EVENT_NAME varchar2(128), FACE_SEQUENCE varchar2(27), FACTOR_B number, FACTOR_C number, FALSEM float, FALSEX float, FALSEY float, FALSEZ float, FAMILY_NAME varchar2(257), FB_COUNT number(38,0), FB_FCOUNT number(38,0), FB_KBYTES number(38,0), FB_PARTIAL number(38,0), FEATURE_NAME varchar2(24), FILTERUITSTROMING nvarchar(2), FLAGS number(38,0), FLEXIBELEWATERKERINGID varchar2(38), FLUX number(8,2), FORWARDLABEL nvarchar(257), FREEZE_MODE varchar2(16), FREEZE_OWNER varchar2(128), FREEZE_STATUS varchar2(8), FREEZE_WRITER varchar2(128), FREQUENTIE number(10,0), FROM_DATE nvarchar(128), FROM_SRID number, FUNCTIEAFSLUITMIDDEL number(3,0), FUNCTIEGEMAAL number(5,0), FUNCTIEOPPERVLAKTEWATERDEEL number(3,0),
      FUNCTION varchar2(128), FYSIEKAANWEZIG nvarchar(1), F_GEOMETRY_COLUMN varchar2(260), F_TABLE_CATALOG nvarchar(128), F_TABLE_NAME varchar2(260), F_TABLE_SCHEMA varchar2(260), GEDRAGGRASZODEBUITENTALUD number(5,0), GELDIGBEGINTIJD timestamp(6), GELDIGEINDTIJD timestamp(6), GEMAALID varchar2(38), GEMEENTE varchar2(100), GEMIDDELDHOOGWATER number(8,2), GEOG_CRS_DATUM_ID number(10,0), GEOMETRY_COLUMN varchar2(2048), GEOMETRY_TYPE number, GEOM_ID number(38,0), GEONAUWKEURIGHEIDXY number(38,0), GERELATEERDAFAANVOERGEBIED number(10,0), GETIJDEBEINVLOED nvarchar(1), GEWENSTPERCENTAGEMORTEL number(7,2), GRADENBOCHT number(10,0), GRANTABLE varchar2(3), GRANTEE varchar2(128), GRANTOR varchar2(128), GRAPH_FLAG varchar2(22), GRAPH_WORKSPACE varchar2(128), GRASKWALITEIT number(5,0), GREENWICH_LONGITUDE float, GRONDSOORTZODE number(5,0), GRONDWATERKOPPELLIJNID char(38),
      GRONDWATERKOPPELPUNTID char(38), GROUPNAME varchar2(128), GROUP_COL_NUM number, GROUP_KEY_HIGH blob, GROUP_KEY_LOW blob, GROUP_TYPE varchar2(5), GRP_ID number, GSIZE1 float, GSIZE2 float, GSIZE3 float, G_TABLE_CATALOG nvarchar(128), G_TABLE_NAME varchar2(260), G_TABLE_SCHEMA varchar2(260), HECTOMETERAANDUIDING nvarchar(50), HEEFTRIOOLOVERSTORT nvarchar(1), HELLING number(5,0), HISTORY varchar2(22), HISTORY_REGID number(38,0), HOEKVANGOLFINVAL number(8,2), HOEVEELHEIDBESTORTING number(10,0), HOOGSTEDOORSTROOMHOOGTE number(8,2), HOOGTE number(7,3), HOOGTEBINNENONDERKANTBEN number(8,2), HOOGTEBINNENONDERKANTBENE number(8,2), HOOGTEBINNENONDERKANTBOV number(8,2), HOOGTEBINNENONDERKANTLEIDING number(38,8), HOOGTEBOUWWERK number(38,8), HOOGTEBOVENKANT number(8,2), HOOGTEBOVENZIJDE number(8,2), HOOGTECONSTRUCTIE number(8,2),
      HOOGTEINWENDIG number(5,0), HOOGTEONDERZIJDE number(8,2), HOOGTEOPENING number(8,2), HOOGTEPUTBODEM number(38,8), HOOGTEPUTDEKSEL number(38,8), HORIZONTALEKNIK number(10,0), HYDRAULISCHECAPACITEIT number(10,0), HYDRAULISCHERANDVOORWAARDEID char(38), HYDROOBJECTGROEPERINGID char(38), HYDROOBJECTID char(38), IBAID char(38), ID number, IDX varchar2(3), IDX_NAME varchar2(128), IDX_OWNER varchar2(128), IDX_TABLE_NAME varchar2(128), IDX_TYPE varchar2(27), IMAGE blob, IMPLICIT varchar2(3), IMV_VIEW_NAME nvarchar(128), INDEXPTNIDEN number, INDEX_ID number(38,0), INDEX_NAME varchar2(130), INDEX_OWNER varchar2(128), INDEX_TYPE number(38,0), INDICATIEDOORVAARBAARHEID nvarchar(1), INDICATIEWATERKEREND number(5,0), INDPEILREGULPEILSCHEIDEND varchar2(100), INDX_DIMS number, INFILTRATIEFACTOR number(8,2),
      INFILTRATIEVOORZIENING nvarchar(1), INFORMATION_SOURCE varchar2(254), INGEWASSEN nvarchar(1), INHOUD number(7,2), INHOUDVOORZIENINGREGEN number(10,2), INHOUDVOORZIENINGVOLUME number(10,2), INONDERZOEK varchar2(100), INS varchar2(3), INSPECTED varchar2(1), INSTALLED_BY_ORACLE number(1,0), INSTANCE_ID number(38,0), INSTANCE_NAME nvarchar(128), INST_ID number, INS_BB_END1 number, INS_BB_END2 number, INS_BB_END3 number, INS_BB_END4 number, INS_BB_START1 number, INS_BB_START2 number, INS_BB_START3 number, INS_BB_START4 number, INS_NO number, INTREEVERLIES number(8,2), INVERSE_FLATTENING number, INV_FLATTENING number, INWINNENDEINSTANTIE nvarchar(5), INWINNINGSINSTANTIE nvarchar(50), INWINNINGSMETHODE number(5,0), INWONEREQUIVALENTBEDRIJVEN number(10,0), INWONEREQUIVALENTINWONERS number(10,0),
      INWONEREQUIVALENTRECREATIE number(10,0), INWONERSEQUIVALENTBEDRIJVEN number(8,0), INWONERSEQUIVALENTINWONERS number(10,0), INWONERSEQUIVALENTRECREATIE number(8,0), ISCONTAINMENT number(4,0), ISREFRESHED varchar2(3), ISZINKER nvarchar(1), IS_EXCLUDED number(38,0), IS_GEODETIC number, IS_IMPLEMENTED number(1,0), IS_IMPLEMENTED_FORWARD number(1,0), IS_IMPLEMENTED_REVERSE number(1,0), IS_INTERNAL varchar2(4), IS_LEGACY varchar2(5), IS_ONLINE varchar2(3), IS_SPATIAL varchar2(1), IS_VALID varchar2(5), ITEMINFO number(38,0), JAARGELEGD number(10,0), JAARTM number(10,0), JAARVAN number(10,0), JAARVANAANLEG number(4,0), JAARVASTSTELLING number(10,0), KATHODISCHEBESCHERMINGID varchar2(38), KERENDEHOOGTE number(8,2), KERNOPBOUWID char(38), KEYWORD nvarchar(32), KLEIKWALITEIT number(5,0), KORRELVERDELING number(8,2), KORRELVERDELINGKLEILAAG number(7,2),
      KORRELVERDELINGZANDLAAG number(7,2), KRUINBREEDTE number(8,2), KRWSTILSTAANDID char(38), KRWSTROMENDID char(38), LAAGSTEDOORSTROOMHOOGTE number(8,2), LAATSTERENOVATIE timestamp(6), LAST_ANALYZED timestamp(6), LAST_EDITED_USER nvarchar(255), LAST_MODIFIED_COUNT number(38,0), LAST_RECONCILE_MOMENT timestamp(3), LATERALEKNOOPID varchar2(38), LAYER_CONFIG nvarchar(32), LAYER_GTYPE number, LAYER_ID number(38,0), LAYER_MASK number(38,0), LAYER_SRID number, LEAF_BLOCKS number, LEDIGINGSMETHODE nvarchar(50), LEDIGINGSTIJD number(10,0), LEGACY_CODE number(10,0), LEGACY_NAME varchar2(50), LEGACY_PARAM_NAME varchar2(80), LEGACY_UNIT_NAME varchar2(80), LEGACY_WKTEXT varchar2(2046), LEIDINGID varchar2(38), LEIDINGSEGMENTID varchar2(38), LENGTE number(8,2), LENGTEBOUWWERK number(38,8), LENGTEOPENING number(8,2), LENGTESTELSEL number(10,0),
      LIGGING varchar2(50), LINEAGE_ID number(38,0), LINEAGE_NAME number(38,0), LINK xmltype, LINK_FORM varchar2(8), LINK_TYPE varchar2(8), LOAD_ORDER number, LOCATIE nvarchar(100), LOCATOR_ID number(38,0), LOCKING_STATE varchar2(4000), LOCK_DURATION number(38,0), LOCK_MODE varchar2(19), LOCK_OWNER varchar2(4000), LOCK_TIME date, LOCK_TYPE char(1), LOGDATE timestamp(6), LOGFILE_DATA_DB nvarchar(128), LOGFILE_DATA_ID number(38,0), LOGFILE_DATA_OWNER nvarchar(128), LOGFILE_DATA_TABLE nvarchar(418), LOGFILE_ID number(38,0), LOGFILE_NAME nvarchar(418), LOKATIEGRASBEKLEDING number(5,0), LONG_PREDICATE varchar2(3), LONG_VAL number(38,0), MAATGEVENDHOOGWATER number(8,2), MAJOR number(38,0), MAP_ADAPTER blob, MAP_BASE_SCALE number, MAXIMALECAPACITEIT number(8,2),
      MAXIMALECAPACITEITUURDWA number(10,0), MAXIMALEPOMPCAPACITEIT number(10,0), MAXM float, MAXX float, MAXY float, MAXZ float, MAX_M float, MAX_PPR number, MAX_X float, MAX_Y float, MAX_Z float, MCLUSTER_TOL float, MEETINSTRUMENTID varchar2(38), MEETLOCATIEID char(38), MEETNETID char(38), MESSAGE varchar2(1999), METENDEINSTANTIE nvarchar(100), METINGOMSCHRIJVING nvarchar(250), MILIEUZONE number(38,8), MINIMALECAPACITEIT number(8,2), MINIMUM_ID number(38,0), MINM float, MINOR number(38,0), MINX float, MINY float, MINZ float, MIN_M float, MIN_X float, MIN_Y float, MIN_Z float,
      MP_LEAF_WORKSPACE varchar2(128), MP_ROOT_WORKSPACE varchar2(128), MP_ROOT_WORKSPACE_ID number, MSG_TIME timestamp(6), MSG_TYPE varchar2(20), MUNITS float, MUURVLAK number(3,0), M_OFFSET float, M_SCALE float, NAME varchar2(130), NAP_BOUT nvarchar(500), NATTEOMTREK number(8,2), NATUURVRIENDELIJKEOEVERID varchar2(38), NAUWKEURIGHEID number(8,2), NAUWKEURIGHEIDXY number(2,0), NAUWKEURIGHEIDZ number(2,0), NIVEAU number(3,0), NODENAME nvarchar(256), NODE_SEQUENCE varchar2(27), NOMINALESPANNING number(10,0), NOODUITLAATID char(38), NORM nvarchar(50), NORMGEPARAMPROFIELID varchar2(38), NORMGROEP number(5,0), NORMKADER number(5,0), NORMWAARDE nvarchar(50), NOTIFICATION varchar2(3), NOTIFYWORKSPACES varchar2(0), NTV2_FILE_ID number, NUMLOCKS number(38,0),
      NUM_IDS number(38,0), NUM_MBRS number, NUM_NULLS number, NUM_PROP_VALUE number(38,0), NUM_ROWS number, O90 number(8,2), OBJECT_FLAGS number(38,0), OBJECT_ID number(38,0), OBJECT_NAME nvarchar(160), OBJECT_OWNER nvarchar(128), OBJECT_TYPE number(38,0), OMSCHRIJVING nvarchar(50), OMSCHRIJVINGLOCATIE nvarchar(50), ONDERHOUDOPPEIL varchar2(100), ONDERLAAG number(5,0), ONEFFENHEDENHAVENDAM number(8,2), ONTSTAANSWIJZE number(3,0), ONTTREKKINGVOORMENSELIJKECONS varchar2(100), ONTWERPBUITENWATERSTAND number(8,2), OPCOUNT number(38,0), OPENINGSPEIL number(8,2), OPENKEERPEIL number(8,2), OPERATION number, OPERATIONELESPANNING number(10,0), OPPERVLAKBEDRIJFSTERREIN number(8,2), OPPERVLAKTE number(12,0), OPPERVLAKTECOMPARTIMENT number(38,8), OPPERVLAKTEWATERLICHAAMID char(38), OPPWATERVOLGNUMMER number(8,0), OPSTELLINGPOMP number(5,0),
      OPTALUD varchar2(100), OPTIMAL_ARRAY_SIZE number(38,0), OP_PATH_STEP number(5,0), ORDECODE varchar2(100), ORDER number(5,0), ORDESCOPE number(5,0), ORDESYSTEMATIEK number(5,0), ORGANIZATION nvarchar(128), ORG_COORDSYS_ID number(38,0), ORIGINID char(38), ORIGITEMTYPEID char(38), OVERNAMEPUNTID varchar2(38), OVERSTORTFREQUENTIE number(5,0), OVERSTORTMESAANWEZIG nvarchar(50), OWNER varchar2(130), PACKAGE varchar2(128), PAKKING nvarchar(50), PARAMETER_ID number(10,0), PARAMETER_NAME varchar2(80), PARAMETER_VALUE float, PARAM_SIGN_REVERSAL varchar2(3), PARAM_VALUE_FILE clob, PARAM_VALUE_FILE_REF varchar2(254), PARAM_VALUE_XML xmltype, PARENTTYPEID char(38), PARENT_FLAG varchar2(17), PARENT_ID number, PARENT_NAME nvarchar(64), PARENT_OWNER nvarchar(128), PARENT_SAVEPOINT varchar2(128),
      PARENT_SDE_ID number(38,0), PARENT_STATE_ID number(38,0), PARENT_VERSION number(38,0), PARENT_VERSION_ID number(38,0), PARENT_WORKSPACE varchar2(128), PARENT_WORKSPACE_ID number(38,0), PARENT_WORKSPACE_NAME varchar2(128), PARTITION_NAME nvarchar(128), PATH nvarchar(770), PEILAFWIJKINGGEBIEDID char(38), PEILBESLUITGEBIEDID char(38), PEILGEBIEDPRAKTIJKID char(38), PEILGEBIEDVIGERENDID char(38), PERCENTAGEBITUMEN number(7,2), PERCENTAGEHOLLERUIMTE number(7,2), PERCENTAGESTEENSLAGGRIND number(7,2), PERCENTAGEVULSTOF number(7,2), PERCENTAGEZAND number(7,2), PERSISTENTIE number(3,0), PF_OWNER varchar2(128), PHYSICALNAME nvarchar(257), PIEKPERIODEOFGOLFPERIODE number(8,2), PLAATSOPMAATLATDOELSTELLING varchar2(500), PLUSFYSIEKVOORKOMEN number(3,0), PLUSTYPE number(3,0), POLICY_GROUP varchar2(128), POLICY_NAME varchar2(128), POLICY_TYPE varchar2(24), POMPCURVE nvarchar(256), POMPOVERCAPACITEITBESCHIKBAAR number(38,8),
      POMPRICHTING number(5,0), POROSITEIT number(8,2), POSITION number, PREDICATE1 clob, PREDICATE2 clob, PREVIOUS_ANCESTOR_MOMENT timestamp(3), PRIME_MERIDIAN_ID number(10,0), PRIME_MERIDIAN_NAME varchar2(80), PRIORITY number, PRIVILEGE varchar2(23), PROJECTION_CONV_ID number(10,0), PROPERTIES clob, PROPERTY nvarchar(32), PROP_NAME nvarchar(32), PROP_VALUE nvarchar(255), PROVINCIEREGLEMENT nvarchar(5), PROXY_YN varchar2(1), PT_COLS varchar2(4000), PT_NAME varchar2(128), PT_OWNER varchar2(128), PUTBODEM number(38,8), PUTID char(38), RANDVOORZIENINGID char(38), RASTERCOLUMN_ID number(38,0), RASTERCOLUMN_MASK number(38,0), RASTER_COLUMN nvarchar(128), RCOUNT number(38,0), RECORD_ID number(38,0), REFERENTIENRCBS number(10,0), REFERENTIEPUNTID char(38),
      REFERENTIESTELSELID char(38), REFERENTIEVLAK number(3,0), REGENWATERBUFFERCOMPARTIMENTID char(38), REGENWATERBUFFERID char(38), REGISTRATION_DATE number(38,0), REGISTRATION_ID number, RELATIEFOPENOPPERVLAK number(7,2), RELATIEVEHOOGTELIGGING number(4,0), RELEASE number(38,0), REMOVABLE varchar2(3), REPLICAID number(38,0), RES xmltype, RESID raw(16), RESOLVE_STATUS varchar2(8), RESOLVE_USER varchar2(128), RETIRETIME timestamptz(6), REVERSE_OP number(1,0), RICHTING number(5,2), RIC_NAME varchar2(128), RID number(38,0), RIOLERINGSGEBIEDID char(38), RIOLERINGSGEBIEDIDBRON char(38), RIOLERINGSGEBIEDIDDOEL char(38), RIOOLGEMAALID varchar2(38), RIOOLOVERSTORTID char(38), RIOOLVREEMDWATER number(38,8), ROLE varchar2(128), ROOT_COL_NAME varchar2(128), ROOT_TABLE_NAME varchar2(128), ROOT_TABLE_OWNER varchar2(128),
      ROTATE_X number, ROTATE_Y number, ROTATE_Z number, ROWID_COLUMN nvarchar(128), RUIMTELIJKEAFBAKENINGBEKEND nvarchar(1), RULE_NAME varchar2(64), RUWHEID number(8,2), RUWHEIDHOOG number(8,2), RUWHEIDLAAG number(8,2), RWZIID varchar2(38), R_CONSTRAINT_NAME varchar2(128), SAMPLE_SIZE number, SAVEPOINT varchar2(128), SCALE_ADJUST number, SCENE_NAME varchar2(130), SCHAAL number(10,0), SCHADELIJKEBEGROEIING number(5,0), SCHEMA_NAME varchar2(128), SCHEMA_URL varchar2(700), SDESVR_REL_LOW number(38,0), SDE_ID number(38,0), SDE_ROW_ID number(38,0), SDE_STATE_ID number, SDE_TYPE number(38,0), SDE_XML_ID number(38,0), SDO_COLUMN_NAME varchar2(2048), SDO_COMMIT_INTERVAL number, SDO_DML_BATCH_SIZE number, SDO_FIXED_META raw(255), SDO_INDEX_DIMS number,
      SDO_INDEX_GEODETIC varchar2(8), SDO_INDEX_NAME varchar2(130), SDO_INDEX_OBJNO number, SDO_INDEX_OWNER varchar2(130), SDO_INDEX_PARTITION varchar2(130), SDO_INDEX_PRIMARY number, SDO_INDEX_STATUS varchar2(32), SDO_INDEX_TABLE varchar2(130), SDO_INDEX_TYPE varchar2(32), SDO_INDEX_VERSION number, SDO_INITIAL_EXTENT varchar2(32), SDO_LAYER_GTYPE varchar2(32), SDO_LEVEL number, SDO_MASK char(9), SDO_MAXLEVEL number, SDO_MAX_EXTENTS number, SDO_MESSAGE varchar2(1000), SDO_MIN_EXTENTS number, SDO_NEXT_EXTENT varchar2(32), SDO_NL_INDEX_TABLE varchar2(131), SDO_NUMTILES number, SDO_NUM_BLKS number, SDO_NUM_ROWS number, SDO_OPTIMIZED_NODES number, SDO_PARTITIONED number, SDO_PARTITION_NAME varchar2(130), SDO_PCTINCREASE number, SDO_RELATION varchar2(30), SDO_RTREE_DIMENSIONALITY number, SDO_RTREE_ENT_XPND number,
      SDO_RTREE_FANOUT number, SDO_RTREE_HEIGHT number, SDO_RTREE_NUM_NODES number, SDO_RTREE_PCTFREE number, SDO_RTREE_QUALITY number, SDO_RTREE_READ_ONLY number, SDO_RTREE_ROOT varchar2(32), SDO_RTREE_SEQ_NAME varchar2(130), SDO_SEQUENCE number, SDO_SID number, SDO_SRID number, SDO_SYSTEM_NAME varchar2(130), SDO_TABLESPACE varchar2(130), SDO_TABLE_NAME varchar2(130), SDO_TIMESTAMP timestamptz(3), SDO_TSNAME varchar2(130), SDO_TXN_IDX_ID varchar2(32), SDO_UNIT varchar2(80), SDO_USER varchar2(130), SEARCH_CONDITION clob, SECONDARY_SRID number(38,0), SEGMENTBREEDTE number(8,2), SEL varchar2(3), SEMI_MAJOR_AXIS number, SEMI_MINOR_AXIS number, SEQUENCE_NUMBER number, SERVER_ID number(38,0), SERVICE_NAME varchar2(512), SESSION_DURATION varchar2(3), SESSION_ID char(38),
      SESSION_TAG number(38,0), SE_ANNO_CAD_DATA blob, SHARDGROUP_NAME varchar2(4000), SHARDSPACE_NAME varchar2(128), SHARD_COL_NUM number, SHARD_KEY_HIGH blob, SHARD_KEY_LOW blob, SHARD_LEVEL number(1,0), SHARD_NAME varchar2(159), SHARD_TYPE varchar2(5), SHIFT_X number, SHIFT_Y number, SHIFT_Z number, SHORT_NAME varchar2(80), SHOW_OPERATION number(3,0), SID number, SIGNALERINGSPEIL number(8,2), SIGNIFICANTEGOLFHOOGTE number(8,2), SINGLE_OPERATION_ID number(10,0), SINGLE_OP_SOURCE_ID number(10,0), SINGLE_OP_TARGET_ID number(10,0), SI_FEATURE_NAME varchar2(100), SI_FORMAT varchar2(1400), SI_SOURCE_FORMAT varchar2(1400), SI_SUPPORTED_VALUE number(38,0), SI_TARGET_FORMAT varchar2(1400), SI_VALUE varchar2(255), SLIBBELASTING number(38,8), SLUISID varchar2(38), SLUITPEIL number(8,2),
      SOORTAANDRIJVING number(3,0), SOORTAFSLUITER number(5,0), SOORTAFSLUITMIDDEL number(3,0), SOORTAFVOERAANVOERGEBIED varchar2(100), SOORTBEKLEDINGCONSTRUCTIE varchar2(100), SOORTELIJKEMASSASTENEN number(8,2), SOORTGELOOSDWATER number(5,0), SOORTKABEL number(5,0), SOORTKATHODE number(5,0), SOORTKWANTITEITSMETING number(3,0), SOORTLEIDING number(2,0), SOORTMATERIAAL number(5,0), SOORTMATERIAALOEVER number(3,0), SOORTMEETINSTRUMENT number(5,0), SOORTMEETNET number(3,0), SOORTNATUURVRIENDELIJKEOEVER number(3,0), SOORTOPPWATERKWALITEIT number(3,0), SOORTOPPWATERKWANTITEIT number(3,0), SOORTOVERSPANNING number(3,0), SOORTOVERSTORT number(2,0), SOORTPARAMETER number(3,0), SOORTPEILMERK number(3,0), SOORTPROFIEL number(3,0), SOORTRANDVOORZIENING number(2,0), SOORTREFERENTIELIJN number(5,0), SOORTREGELBAARHEID number(3,0), SOORTREGENWATERBUFFER number(5,0), SOORTRIOOLGEMAAL number(2,0), SOORTSLUIS number(3,0), SOORTSTELSEL number(2,0),
      SOORTSTREEFPEIL number(3,0), SOORTSTUW number(3,0), SOORTTAAK number(38,0), SOORTVERBINDINGSSTUK number(5,0), SOORTVERDEDIGING number(3,0), SOORTVISPASSAGE number(3,0), SOORTVUILVANG number(3,0), SOORTWATER number(5,0), SOORTWATERINRICHTINGSELEMENT number(3,0), SOORTZANDVANG number(3,0), SOP_INSTANCE_UID varchar2(128), SORT_ORDER number(5,0), SOURCEBEGINGEN number(38,0), SOURCEENDGEN number(38,0), SOURCE_GEOG_SRID number(10,0), SOURCE_ID raw(16), SOURCE_SRID number(10,0), SOURCE_TYPE varchar2(17), SPATIAL_COLUMN nvarchar(128), SPLEETBREEDTELANGSVOEGEN number(8,2), SPLEETBREEDTESTOOTVOEGEN number(8,2), SPONNINGBREEDTE number(8,2), SQL_STR varchar2(4000), SRID number, SRNUM number, SRSNAME varchar2(2000), SRSNAMESPACE varchar2(2000), SRTEXT varchar2(1000), SR_NAME nvarchar(128), START1 number,
      START2 number, START3 number, START_1 number, START_2 number, START_3 number, START_4 number, START_MOMENT timestamp(3), START_TIME date, STATE number, STATE_ID number(38,0), STATIC_POLICY varchar2(3), STATS_DATE number(38,0), STATUS number(38,0), STATUSKRW varchar2(100), STATUSLEGGERWATERSYSTEEM number(38,0), STATUSONDERHOUD nvarchar(50), STATUSPEILGEBIED number(5,0), STEENDIAMETER nvarchar(8), STORAGE_TYPE number, STRAALBOCHT number(10,0), STROMINGSBEGELEIDING number(5,0), STROOMVOERENDEBREEDTE number(8,2), STR_VAL varchar2(256), STUWID varchar2(38), STYLE_COLUMN varchar2(130), STYLING_RULES clob, SUPPORTS_SDO_GEOMETRY varchar2(5), SYSNAME nvarchar(32), TABFAM_ID number, TABLEPTNIDEN number,
      TABLE_ID number(38,0), TABLE_IMPORT varchar2(3), TABLE_NAME varchar2(128), TABLE_NAME1 varchar2(128), TABLE_NAME2 varchar2(128), TABLE_OWNER varchar2(128), TABLE_SCHEMA varchar2(130), TAB_MERGE_WO_REMOVE varchar2(3), TAB_MERGE_W_REMOVE varchar2(3), TAG_ALIAS number(38,0), TAG_ID number(38,0), TAG_NAME nvarchar(1024), TARGETGEN number(38,0), TARGET_ID raw(16), TARGET_PATH varchar2(4000), TARGET_SRID number(10,0), TARGET_UOM_ID number(10,0), TEENOVERGANGSCONSTRUCTIEID char(38), TERUGSLAGKLEPAANWEZIG nvarchar(50), TEXT_ATTRIBUTES varchar2(4000), TEXT_EXPRESSION varchar2(4000), TG_ID number, TG_LAYER_ID number, TG_LAYER_LEVEL number, TG_LAYER_TYPE varchar2(10), TG_SEQUENCE varchar2(25), THEME_COLUMN varchar2(2048), THEME_TYPE varchar2(32), TILES_TABLE varchar2(130), TIME_LAST_MODIFIED date,
      TOETSPEIL number(8,2), TOLERANCE number, TOPOLOGY varchar2(20), TOPOLOGY_ID number, TOPO_ATTRIBUTE varchar2(100), TOPO_ID number, TOPO_OP varchar2(3), TOPO_SEQUENCE number, TOPO_TYPE number, TOTAL_FEATURES number(38,0), TOTAL_POINTS number(38,0), TO_DATE nvarchar(128), TO_SRID number, TRANSPORTSTELSELID char(38), TRIGGER_BODY clob, TRIGGER_NAME varchar2(128), TRIGGER_OWNER varchar2(128), TRIGGER_TYPE varchar2(4000), TUNNELID char(38), TXNID varchar2(128), TYPE varchar2(32), TYPEBEDIENING number(38,0), TYPEBEKLEDINGLAAG number(5,0), TYPEBODEMLAAG number(5,0), TYPECONSTRUCTIEOPBOUW number(5,0), TYPEDIJKOPBOUW nvarchar(50), TYPEELECTRICITEITSKABEL number(5,0), TYPEFILTERLAAG number(5,0), TYPEHYDRAULISCHOBJECT number(3,0), TYPEIBA number(5,0),
      TYPEINVLOEDSLIJN number(5,0), TYPEKERNOPBOUW number(5,0), TYPEKRUISING number(2,0), TYPEMATERIAAL number(5,0), TYPEMATERIAALAFSLUITMIDDEL number(3,0), TYPEMATERIAALBEKLEDING number(5,0), TYPEMATERIAALDRAINAGEBUIS number(5,0), TYPEMATERIAALZINKSTUK number(5,0), TYPEONDERGROND number(5,0), TYPEONTLUCHTER number(5,0), TYPEOVERBRUGGINGSDEEL number(3,0), TYPEOVERGANGSCONSTRUCTIE number(5,0), TYPEPIGGINGINSTALLATIE number(5,0), TYPEPOMP number(5,0), TYPEPOMPSCHAKELING number(5,0), TYPEPROFIELKENMERK number(5,0), TYPEREFERENTIESTELSEL number(5,0), TYPERUWHEID number(5,0), TYPERWZI number(5,0), TYPEVERBINDING number(5,0), TYPEWATERKERENDECONSTRUCTIE number(5,0), TYPEWATERKERING number(5,0), TYPEWATERKERINGSECTIE number(5,0), TYPEWATERKERINGSTELSEL number(5,0), TYPEWETOFVERORDENING number(3,0), TYPEZONE number(3,0), TYPOLOGIEHUIDIG varchar2(100), TYPOLOGIEREFNATUURLIJK varchar2(100), UITSLAGPEIL number(10,2), UITTREEVERLIES number(8,2),
      UNIQUENESS varchar2(9), UNITFACTOR number, UNIT_NAME varchar2(2083), UNIT_OF_MEAS_NAME varchar2(2083), UNIT_OF_MEAS_TYPE varchar2(50), UOM_ID number(10,0), UOM_ID_SOURCE_OFFSETS number(10,0), UOM_ID_TARGET_OFFSETS number(10,0), UPD varchar2(3), URL nvarchar(255), URN varchar2(1000), URN_POSTFIX varchar2(1000), URN_PREFIX varchar2(1000), USED varchar2(1), USER_IDENTITY nvarchar(255), USER_STATS varchar2(3), USE_CASE varchar2(32), UUID char(38), UUID_VAL char(38), VAARWEGID char(38), VAARWEGKLASSE nvarchar(30), VALIDATION_MOMENT timestamp(3), VALIDTIME varchar2(3), VALUE varchar2(4000), VASTEDAMID char(38), VEGETATIEOBJECTID char(38), VERDEDIGINGID char(38), VERLORENBERGING number(10,2), VERMOGEN number(10,0), VERSION number(38,0),
      VERSION1 number, VERSION2 number, VERSION_ID number(38,0), VERTICALEKNIK number(10,0), VERVAL number(8,2), VERWIJZINGNAARREGLEMENT nvarchar(50), VIOLATION# number, VISPASSAGEID varchar2(38), VOLGNUMMER number(5,0), VOLUMECOMPARTIMENT number(38,8), VOLUMEMATERIAAL number(8,2), VOORDEID char(38), VORM number(5,0), VORMBOUWWERK number(5,0), VORMKOKER number(3,0), VORMLEIDING number(2,0), VUILVANGID char(38), VULLINGSWIJZE number(5,0), VULTIJDGEBIED number(38,8), WAARDE number(8,3), WAARDEMETING number(12,4), WAARDEVALDEFLECTIE number(8,2), WATERAFVOER number(10,0), WATERHOOGTE number(8,3), WATERKERINGSTELSELAGGREGATIEID char(38), WATERSCHAPCODE number(38,0), WATERSTAATSWERKWATERKERINGID varchar2(38), WATERSTAND number(8,2), WCOUNT number(38,0), WEESCONSTRUCTIEID char(38),
      WHEN_CLAUSE varchar2(4000), WKTEXT varchar2(2046), WKTEXT3D varchar2(4000), WORKSPACE varchar2(128), WORKSPACE_ID number(38,0), WORKSPACE_LOCKMODE varchar2(19), WORKSPACE_LOCKMODE_OVERRIDE varchar2(3), WORKSPACE_NAME varchar2(128), WRITERSITE varchar2(128), WSPC_MERGE_WO_REMOVE varchar2(3), WSPC_MERGE_W_REMOVE varchar2(3), WS_BESTORTINGID number(10,0), WS_DUMMY number(10,0), WS_HYDROOBJECTID number(10,0), WS_METADATAID number(10,0), WS_WATERSTAATSWERKWATERKERINGI number(10,0), XDR_NEEDED varchar2(1), XFLAGS number(38,0), XML xmltype, XMLSCHEMA clob, XML_DOC blob, XML_DOC_VAL clob, XMUURVLAKCOORDINAAT number(7,2), XYCLUSTER_TOL float, XYUNITS float, X_OFFSET float, YMUURVLAKCOORDINAAT number(7,2), Y_OFFSET float, ZANDWATERUITTREDING number(5,0), ZCLUSTER_TOL float,
      ZUIVERINGSEENHEIDID char(38), ZUNITS float, Z_OFFSET float, Z_SCALE float
    -> GeometryReplacer

Bookmark: AfvoerAanvoergebied
TestFilter
    DEFAULT_VALUE = <UNFILTERED>
    PASSED_TEST_GROUP_OUTPUT = FIRST
    TEST_LIST = "BOOL_OP,OR,COMPOSITE_TEST,""""""1"""""",TEST_CLAUSE,TEST @Value(fme_feature_type) = afvoergebiedaanvoergebied",AfvoergebiedAanvoergebied,"BOOL_OP,OR,COMPOSITE_TEST,""""""1"""""",TEST_CLAUSE,TEST @Value(fme_feature_type) = hydroobject",Hydroobject
    AfvoergebiedAanvoergebied -> TestFilter_2
    AfvoergebiedAanvoergebied -> AttributeKeeper_2
    Hydroobject -> AttributeKeeper_3
    Hydroobject -> Junction_3
    Hydroobject -> Junction_2
    <UNFILTERED> -> Junction_3
    <UNFILTERED> -> Junction_2

Bookmark: Gerelateerdafvoergebied
TestFilter_2
    DEFAULT_VALUE = <UNFILTERED>
    PASSED_TEST_GROUP_OUTPUT = FIRST
    TEST_LIST = "BOOL_OP,OR,COMPOSITE_TEST,""""""1"""""",TEST_CLAUSE,TEST gerelateerdafaanvoergebied ATTRIBUTE_HAS_A_VALUE """,gerelateerdafaanvoergebied ATTRIBUTE_HAS_A_VALUE
    gerelateerdafaanvoergebied ATTRIBUTE_HAS_A_VALUE -> FeatureJoiner_4 [LEFT]
    <UNFILTERED> -> TestFilter_3
AttributeKeeper_2
    CREATE_BULK_MODE_FEATURES = NO
    KEEP_ATTRS = globalid,objectid
    -> BulkAttributeRenamer_2
BulkAttributeRenamer_2
    ATTRCHOICE = All Attributes
    MODE_CHOICE = RENAME
    PATTERN_ACTION_DISP = ADDPREFIX
    REPLACE_STR = _join_
    -> FeatureJoiner_4 [RIGHT]
FeatureJoiner_4
    ATTR_CONFLICT_RES = Prefer Left
    GEOMETRY_HANDLING = Prefer Left
    JOIN_KEYS = gerelateerdafaanvoergebied _join_objectid AUTO
    JOIN_MODE = Inner
    JOINED -> AttributeCreator_2
AttributeCreator_2
    ATTR_TABLE = SET_TO gerelateerdafaanvoergebied = @Value(_join_globalid)
    -> AttributeRemover_2
AttributeRemover_2
    REMOVE_ATTRS = _join_globalid,_join_objectid
    -> TestFilter_3

Bookmark: Waterafvoer
TestFilter_3
    DEFAULT_VALUE = <UNFILTERED>
    PASSED_TEST_GROUP_OUTPUT = FIRST
    TEST_LIST = "BOOL_OP,OR,COMPOSITE_TEST,""""""1"""""",TEST_CLAUSE,TEST waterafvoer ATTRIBUTE_HAS_A_VALUE """,Waterafvoer
    Waterafvoer -> FeatureJoiner_5 [LEFT]
    <UNFILTERED> -> Junction_2
    <UNFILTERED> -> Junction_3
AttributeKeeper_3
    CREATE_BULK_MODE_FEATURES = NO
    KEEP_ATTRS = globalid,objectid
    -> BulkAttributeRenamer_3
BulkAttributeRenamer_3
    ATTRCHOICE = All Attributes
    MODE_CHOICE = RENAME
    PATTERN_ACTION_DISP = ADDPREFIX
    REPLACE_STR = _join_
    -> FeatureJoiner_5 [RIGHT]
FeatureJoiner_5
    ATTR_CONFLICT_RES = Prefer Left
    GEOMETRY_HANDLING = Prefer Left
    JOIN_KEYS = waterafvoer _join_objectid AUTO
    JOIN_MODE = Inner
    JOINED -> AttributeCreator_3
AttributeCreator_3
    ATTR_TABLE = SET_TO waterafvoer = @Value(_join_globalid)
    -> AttributeRemover_3
AttributeRemover_3
    REMOVE_ATTRS = _join_globalid,_join_objectid
    -> Junction_2
    -> Junction_3

Bookmark: Koppelen domeinwaarden
AttributeExploder
    ATTR_NAME_LABEL = _attr_name
    ATTR_VALUE_LABEL = _attr_value
    EXPLODING_TYPE = Features
    KEEP_ATTRIBUTES = Yes
    KEEP_GEOMETRY = No
    -> AttributeKeeper
AttributeKeeper
    CREATE_BULK_MODE_FEATURES = NO
    KEEP_ATTRS = fme_feature_type,_attr_name,_attr_value,globalid,fme_dataset
    -> TestFilter_4
Note: Check of File geodatabase, dan geen domeinen koppelen
TestFilter_4
    DEFAULT_VALUE = <UNFILTERED>
    PASSED_TEST_GROUP_OUTPUT = FIRST
    TEST_LIST = "BOOL_OP,OR,COMPOSITE_TEST,""""""1"""""",TEST_CLAUSE,CASE_INSENSITIVE_TEST @Value(fme_dataset) ENDS_WITH .gdb",File Geodatabase
    File Geodatabase -> FeatureJoiner_6 [LEFT]
    <UNFILTERED> -> FeatureJoiner_2 [LEFT]
AttributeFilter
    ATTR_NAME = doelDomein
    ATTR_VALUES = <Empty>,<Missing>,<Null>,<Unfiltered>
    <UNFILTERED> -> FeatureJoiner [LEFT]
Domeinwaarden (reader XLSXR_2)
    attributes: doelDomein char(45), doelDomeinWaarde char(18), doelDomeinOmschrijving char(80)
    -> FeatureJoiner [RIGHT]
FeatureJoiner
    ATTR_CONFLICT_RES = Use Left
    GEOMETRY_HANDLING = Use Left
    JOIN_KEYS = doelDomein doelDomein AUTO
    JOIN_MODE = Inner
    JOINED -> FeatureJoiner_2 [RIGHT]
    JOINED -> FeatureJoiner_6 [RIGHT]
FeatureJoiner_2
    ATTR_CONFLICT_RES = Use Left
    GEOMETRY_HANDLING = Use Left
    JOIN_KEYS = fme_feature_type doelObject AUTO _attr_name doelAttribuut AUTO _attr_value doelDomeinWaarde AUTO
    JOIN_MODE = Inner
    JOINED -> AttributeCreator
    <REJECTED> -> FeatureJoiner_2__Rejected_
FeatureJoiner_6
    ATTR_CONFLICT_RES = Use Left
    GEOMETRY_HANDLING = Use Left
    JOIN_KEYS = fme_feature_type doelObject AUTO _attr_name doelAttribuut AUTO _attr_value doelDomeinOmschrijving AUTO
    JOIN_MODE = Inner
    JOINED -> AttributeCreator
    <REJECTED> -> FeatureJoiner_2__Rejected_
Note: Attributen maken voor alle kolommen die in een domein zitten (o.b.v. de waarde van DoelKolom)
AttributeCreator
    ATTR_TABLE = SET_TO @Value(doelAttribuut) = @Value(doelDomeinOmschrijving)
    -> AttributeRemover
Note: Alle Doel... kolommen en _attr_name en _attr_value verwijderen
AttributeRemover
    REMOVE_ATTRS = _attr_name,_attr_value,doelAttribuut,doelAttribuutType,doelDomein,doelDomeinOmschrijving,doelDomeinWaarde,doelObject
    -> Aggregator_2
Note: Aggregeren op fme_feature_type en globalid
Aggregator_2
    ACCUM_ATTRS_NAME = Merge Incoming Attributes
    AGGREGATE_TYPE = Homogeneous Collection (If Possible)
    GROUP_BY = fme_feature_type globalid
    MODE = Geometry - Assemble One Level
    SEP = ,
    AGGREGATE -> FeatureJoiner_3 [LEFT]
FeatureJoiner_2__Rejected_: Inspector [off]
